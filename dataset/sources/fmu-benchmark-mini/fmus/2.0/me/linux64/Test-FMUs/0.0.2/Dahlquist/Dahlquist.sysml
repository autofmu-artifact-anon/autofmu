package Dahlquist {
  // features: x
  // scenarios: [{'kind': 'step', 'start_time': 0.0, 'stop_time': 10.0, 'step_size': 0.1, 'seed': 0}, {'kind': 'ramp', 'start_time': 0.0, 'stop_time': 10.0, 'step_size': 0.1, 'seed': 0}, {'kind': 'sine', 'start_time': 0.0, 'stop_time': 10.0, 'step_size': 0.1, 'seed': 0}]
  part def Dahlquist {
    out port x;
    attribute k;
  }
}
