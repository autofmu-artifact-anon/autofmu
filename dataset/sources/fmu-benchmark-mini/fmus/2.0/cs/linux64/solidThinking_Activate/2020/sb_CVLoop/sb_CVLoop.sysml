package sb_CVLoop {
    // 输入输出端口定义
    port def OutputPort {
        out attribute Output1: Real;
        out attribute Output2: Real;
        out attribute Output3: Real;
        out attribute Output4: Real;
        out attribute Output5: Real;
    }

    // 参数定义
    part def Parameters {
        attribute Ipar_117: Integer;
        attribute Ipar_116: Integer;
        attribute Ipar_115: Integer;
        attribute Ipar_114: Integer;
        attribute Ipar_113: Integer;
        attribute Ipar_112: Integer;
        attribute Ipar_111: Integer;
        attribute Ipar_110: Integer;
        attribute Ipar_109: Integer;
        attribute Ipar_108: Integer;
        attribute Ipar_107: Integer;
        attribute Ipar_106: Integer;
        attribute Ipar_105: Integer;
        attribute Ipar_104: Integer;
        attribute Ipar_103: Integer;
        attribute Ipar_102: Integer;
        attribute Ipar_101: Integer;
        attribute Ipar_100: Integer;
        attribute Ipar_99: Integer;
        attribute Ipar_98: Integer;
        attribute Ipar_97: Integer;
        attribute Ipar_96: Integer;
        attribute Ipar_95: Integer;
        attribute Ipar_94: Integer;
        attribute Ipar_93: Integer;
        attribute Ipar_92: Integer;
        attribute Ipar_91: Integer;
        attribute Ipar_90: Integer;
        attribute Ipar_89: Integer;
        attribute Ipar_88: Integer;
    }

    // 主要部件定义
    part def CVLoop {
        part parameters: Parameters;
        port outputPort: OutputPort;
    }
}
