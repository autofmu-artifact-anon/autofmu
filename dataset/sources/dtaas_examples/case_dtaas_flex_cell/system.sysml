package PkgFlexCell {
  part def Unifmu {
    out prev_q0 : Real;
    out prev_q1 : Real;
    out prev_q2 : Real;
    out prev_q3 : Real;
    out prev_q4 : Real;
    out prev_q5 : Real;
    out prev_q6 : Real;
    out actual_q0 : Real;
    out actual_q1 : Real;
    out actual_q2 : Real;
    out actual_q3 : Real;
    out actual_q4 : Real;
    out actual_q5 : Real;
    out actual_q6 : Real;
    in target_q0 : Real;
    in target_q1 : Real;
    in target_q2 : Real;
    in target_q3 : Real;
    in target_q4 : Real;
    in target_q5 : Real;
    in target_q6 : Real;
    in motion_time : Real;
    in target_x : Integer;
    in target_y : Integer;
    in target_z : Integer;
    in target_x : Real;
    in target_y : Real;
    in target_z : Real;
    in target_rx : Real;
    in target_ry : Real;
    in target_rz : Real;
    out actual_x : Integer;
    out actual_y : Integer;
    out actual_z : Integer;
    out actual_x : Real;
    out actual_y : Real;
    out actual_z : Real;
    out actual_rx : Real;
    out actual_ry : Real;
    out actual_rz : Real;
    out actual_x_0 : Integer;
    out actual_y_0 : Integer;
    out actual_z_0 : Integer;
    out actual_x_0 : Real;
    out actual_y_0 : Real;
    out actual_z_0 : Real;
    out actual_rx_0 : Real;
    out actual_ry_0 : Real;
    out actual_rz_0 : Real;
    out actual_x_1 : Integer;
    out actual_y_1 : Integer;
    out actual_z_1 : Integer;
    out actual_x_1 : Real;
    out actual_y_1 : Real;
    out actual_z_1 : Real;
    out actual_rx_1 : Real;
    out actual_ry_1 : Real;
    out actual_rz_1 : Real;
    out actual_x_2 : Integer;
    out actual_y_2 : Integer;
    out actual_z_2 : Integer;
    out actual_x_2 : Real;
    out actual_y_2 : Real;
    out actual_z_2 : Real;
    out actual_rx_2 : Real;
    out actual_ry_2 : Real;
    out actual_rz_2 : Real;
    out actual_x_3 : Integer;
    out actual_y_3 : Integer;
    out actual_z_3 : Integer;
    out actual_x_3 : Real;
    out actual_y_3 : Real;
    out actual_z_3 : Real;
    out actual_rx_3 : Real;
    out actual_ry_3 : Real;
    out actual_rz_3 : Real;
    out actual_x_4 : Integer;
    out actual_y_4 : Integer;
    out actual_z_4 : Integer;
    out actual_x_4 : Real;
    out actual_y_4 : Real;
    out actual_z_4 : Real;
    out actual_rx_4 : Real;
    out actual_ry_4 : Real;
    out actual_rz_4 : Real;
    out actual_x_5 : Integer;
    out actual_y_5 : Integer;
    out actual_z_5 : Integer;
    out actual_x_5 : Real;
    out actual_y_5 : Real;
    out actual_z_5 : Real;
    out actual_rx_5 : Real;
    out actual_ry_5 : Real;
    out actual_rz_5 : Real;
  }
  part def Rabbitmq {
    out target_x_ur5e : Integer;
    out target_y_ur5e : Integer;
    out target_z_ur5e : Integer;
    out target_x_kuka : Integer;
    out target_y_kuka : Integer;
    out target_z_kuka : Integer;
    out command_move_ur5e : Boolean;
    out command_move_kuka : Boolean;
    out motion_time_ur5e : Real;
    out motion_time_kuka : Real;
  }
  part def SystemFlexCell {
    part kuka : Unifmu;
    part rabbitmq : Rabbitmq;
    part ur5e : Unifmu;
    connect rabbitmq.target_z_kuka to kuka.target_z;
    connect rabbitmq.target_x_ur5e to ur5e.target_x;
    connect rabbitmq.target_y_ur5e to ur5e.target_y;
    connect rabbitmq.target_y_kuka to kuka.target_y;
    connect rabbitmq.target_z_ur5e to ur5e.target_z;
    connect rabbitmq.target_x_kuka to kuka.target_x;
    connect rabbitmq.motion_time_ur5e to ur5e.motion_time;
    connect rabbitmq.motion_time_kuka to kuka.motion_time;
  }
}
